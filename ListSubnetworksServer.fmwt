FME workspace ListSubnetworksServer.fmwt
Title: Helper workspace for Utility Network
Description: This helper workspace uses layer 500002 or the Subnetwork Table of the Utility Network dataset to return the following:
List of Domain
List of Tier
List of Subnetwork
Subnetwork ISDIRTY or Not
This workspace uses the ArcGIS Server Feature Service format reader which is new in Pro 3.1.
Usage: Read the workspace notes for usage.
History: 10/5/2023,rsalvaleon,Published in Git

Parameters:
- HostUrl = https://utilitynetwork.esri.com/   # https Host URL
- PortalUser = unadmin   # Portal User
- PortalPassword =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   # Enter a Password

Note: Generate Token
Note: EsriPortalTokenGetter downloaded from FME Hub
EsriPortalTokenGetter
    Expiration = 1440
    PortalPassword = $(PortalPassword)
    PortalURL = $(HostUrl)
    PortalUser = $(PortalUser)
    PortalWebadaptor = portal
    -> FeatureReader [INITIATOR]
Note: FeatureReader [FeatureReader] / Reading: / Reader: / Dataset: $(HostUrl)/server/rest/services/NapervilleElectric31_SQLServer/FeatureServer/ / Coordinate System: <not set> / Constraints: / Feature Types to Read: Subnetworks / Feature Type Separator: SPACE / WHERE Clause: <not set> / Spatial Filter: <No Spatial Filter> / Max Features to Read: <not set> / Schema/Data Features: / Features to Read: Schema and Data Features / Output: / Output Ports: / [x] One per Feature Type Regenerate: No / Attribute and Geometry Handling: / Accumulation Mode: Only Use Result / Geometry: Use Result / <Generic> Port: / Attributes to Expose: CREATIONDATE CREATOR DESCRIPTION DOMAINNETWORKNAME FEATUREASSETGROUP FEATUREASSETTYPE FEATUREGLOBALID FEATURESOURCEID FEATURESOURCEID_resolved FEATURETERMINALID GLOBALID ISDELETED ISDELETED_resolved I ... / ARCGISFEATURES Resolve Domains: Yes / ARCGISFEATURES Features Per Request: 1000 / ARCGISFEATURES Token: @Value(token) / ARCGISFEATURES Authentication Type: Provide Token / ARCGISFEATURES Verify HTTPS Certificates: Yes / ARCGISFEATURES Additional Attributes to Expose: <not set>
FeatureReader
    ARCGISFEATURES_AUTH_TYPE = provide_token
    ARCGISFEATURES_CREATE_FEATURE_TABLES_FROM_DATA = Yes
    ARCGISFEATURES_FEATURES_PER_REQUEST = 1000
    ARCGISFEATURES_FORMAT_GUID = YES
    ARCGISFEATURES_QUERY_FEATURE_TYPES_FOR_MERGE_FILTERS = Yes
    ARCGISFEATURES_RESOLVE_DOMAINS = Yes
    ARCGISFEATURES_TOKEN = @Value(token)
    ARCGISFEATURES_USE_SEARCH_ENVELOPE = NO
    ARCGISFEATURES_VERIFY_HTTPS = Yes
    ATTRIBUTES =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
    ATTRS_TO_EXPOSE = CREATIONDATE CREATOR DESCRIPTION DOMAINNETWORKNAME FEATUREASSETGROUP FEATUREASSETTYPE FEATUREGLOBALID FEATURESOURCEID FEATURESOURCEID_resolved FEATURETERMINALID GLOBALID ISDELETED ISDELETED_resolved ISDIRTY ISDIRTY_resolved LASTACKEXPORTSUBNETWORK LASTUPDATE LASTUPDATESUBNETWORK NOTES OBJECTID SUBNETLINEGLOBALID SUBNETWORKCONTROLLERNAME SUBNETWORKNAME TIERNAME TIERRANK TIERTOPOLOGYTYPE TIERTOPOLOGYTYPE_resolved UPDATEDBY
    ATTR_ACCUM_MODE = Only Use Result
    COMBINE_GEOM = Use Result
    DATASET = $(HostUrl)/server/rest/services/NapervilleElectric31_SQLServer/FeatureServer/
    FEATURETYPES = Subnetworks
    FORMAT = ARCGISFEATURES
    INTERACT = NONE
    OUTPUT_FEATURES_DISPLAY = Schema and Data Features
    Subnetworks -> AttributeManager
AttributeManager
    -> Sorter
Sorter
    SORT_PARM = TIERNAME NUMERIC ASCENDING SUBNETWORKNAME ALPHA ASCENDING
    SORTED -> TestFilter
    SORTED -> StatisticsCalculator_2
    SORTED -> StatisticsCalculator
    SORTED -> StatisticsCalculator_3
Note: List of Domain
StatisticsCalculator_2
    CALCULATION_MODE = NUMERIC
    FEAT_STATS = DOMAINNETWORKNAME,NUMERIC_MODE,,,,,,,NUMERIC,,,,,,
    GROUP_BY = DOMAINNETWORKNAME
Note: List of Tiers
StatisticsCalculator
    CALCULATION_MODE = NUMERIC
    FEAT_STATS = TIERNAME,NUMERIC_MODE,,,,,,,NUMERIC,,,,,,
    GROUP_BY = TIERNAME
Note: List of Subnetwork
StatisticsCalculator_3
    CALCULATION_MODE = NUMERIC
    FEAT_STATS = SUBNETWORKNAME,NUMERIC_MODE,,,,,,,NUMERIC,,,,,,
    GROUP_BY = SUBNETWORKNAME DOMAINNETWORKNAME TIERNAME SUBNETWORKCONTROLLERNAME
TestFilter
    DEFAULT_VALUE = <UNFILTERED>
    PASSED_TEST_GROUP_OUTPUT = FIRST
    TEST_LIST = "BOOL_OP,OR,COMPOSITE_TEST,""""""1"""""",TEST_CLAUSE,TEST @Value(ISDIRTY) = 0",@Value(ISDIRTY) = 0
    @Value(ISDIRTY) = 0 -> Validated_Subnetworks
    <UNFILTERED> -> SUBNETWORK_ISDIRTY
Validated_Subnetworks: Logger
    LOG_FEATURE = LOG_ONLY
    MAXCOORDS = 20
    MAXFEATS = 20
    MESSAGE = Feature is:
    SEVERITY = INFO
SUBNETWORK_ISDIRTY: Logger
    LOG_FEATURE = LOG_ONLY
    MAXCOORDS = 20
    MAXFEATS = 20
    MESSAGE = Feature is:
    SEVERITY = INFO

FME custom transformer EsriPortalTokenGetter
Generate an ArcGIS Enterprise Portal service token.
This transformer uses your portal's REST API to generate a service token you can use in subsequent operations requiring one.  For example if you construct an HTTP request to call an administrative or secured endpoint you can include the token.
Enter your portal base URL, web adaptor name, credentials and token expiration lifespan in minutes.
See this topic for background on ArcGIS URL components

Parameters:
- PortalURL = https://webadaptorhost.domain.com   # https Portal Base URL
- PortalWebadaptor = portal   # Portal Webadaptor
- PortalUser = portal_user   # Portal User
- PortalPassword =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   # Enter a Password
- Expiration = 60   # Expiration Duration

Creator
    GEOMTYPE = Geometry Object
    NUM = 1
    CREATED -> AttributeManager_2
AttributeManager_2
    ATTR_TABLE:
      SET_TO PortalURL = $(PortalURL)
      SET_TO PortalWebadaptor = $(PortalWebadaptor)
      SET_TO PortalUser = $(PortalUser)
      SET_TO PortalPassword = $(PortalPassword)
      SET_TO ExpirationMinutes = $(Expiration)
    -> EsriPortalTokenGetter
EsriPortalTokenGetter: PythonCaller
    NEW_ATTRIBUTES = token
    PYTHONSOURCE:
      import fme
      import fmeobjects
      import requests

      class FeatureProcessor(object):
          def __init__(self):
              pass
          def input(self, feature):
              portal = feature.getAttribute('PortalURL')
              webadaptor = feature.getAttribute('PortalWebadaptor')
              url = '/'.join([portal,webadaptor,'sharing','rest','generateToken'])
              referer = portal
              body = {'username': feature.getAttribute('PortalUser'),
              'password': feature.getAttribute('PortalPassword'),
              'client': 'referer',
              'referer': referer,
              'f': 'json',
              'expiration': feature.getAttribute('ExpirationMinutes')}
              response = requests.post(url, headers={}, data=body).json()
              token = str(response['token'])
              feature.setAttribute('token',token)
              self.pyoutput(feature)
          def close(self):
              pass
          def process_group(self):
              pass
    PYTHONSYMBOL = FeatureProcessor
    -> AttributeKeeper
AttributeKeeper
    CREATE_BULK_MODE_FEATURES = NO
    KEEP_ATTRS = token
    -> Output (output)
Output (output)
