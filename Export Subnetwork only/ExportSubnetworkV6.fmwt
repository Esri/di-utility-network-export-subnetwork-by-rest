FME workspace ExportSubnetworkV6.fmwt
Title: Export Subnetwork UNv6
Description: Please see ESRI Git repo for details on this workspace solution .
Usage: Read readme.md for usage and suggested notes to reconfigure the solution to your own utility network.
History: Published in ESRI Github,10/5/2006,rsalvaleon,

Parameters:
- HostUrl = https://utilitynetwork.esri.com/   # https Host URL
- SubnetworkName = RMT007   # Subnetwork
- PortalUser = unadmin   # Portal User
- PortalPassword =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   # Enter a Password

Note: Generate Token
Note: EsriPortalTokenGetter downloaded from FME Hub
EsriPortalTokenGetter
    Expiration = 1440
    PortalPassword = $(PortalPassword)
    PortalURL = $(HostUrl)
    PortalUser = $(PortalUser)
    PortalWebadaptor = portal
    -> ExportSubnetwork

Bookmark: 1-Export Subnetwork
Note: HTTPCaller [HTTPCaller] / Request: / Request URL: $(HostUrl)/server/rest/services/NapervilleElectric31_SQLServer/UtilityNetworkServer/exportSubnetwork / HTTP Method: GET / Query String Parameters: / Name / Value / token / @Value(token) / subnetworkName / $(SubnetworkName) / f / pjson / gdbVersion / sessionId / moment / domainNetworkName / Electric / tierName / Electric Distribution / exportAcknowledgement / traceConfiguration / {"includeContainers":true ,"includeContent":true,"includeStructures":true,"includeBarriers":true,"validateConsistency":true,"includeIsolated&quot ... / resultTypes / [ / { / "type": "features", / "includeGeometry": true, / "includeDomainDescriptions" : true, / ... / Response: / Save Response Body To: Attribute / Save Response Body To Attribute: / Response Body Attribute: _serverResponse / Response Body Encoding: <Auto Detect from HTTP Headers> / SSL/TLS Options: / Verify SSL Certificates: Yes / Minimum Encryption Strength: Use Operating System Default Settings
ExportSubnetwork: HTTPCaller
    ADDITIONAL_URL_PARAMETERS:
      token;@Value(token) subnetworkName;$(SubnetworkName) f;pjson gdbVersion; sessionId; moment; domainNetworkName;Electric tierName;Electric Distribution exportAcknowledgement; traceConfiguration;{
      	"includeContainers": true,
      	"includeContent": true,
      	"includeStructures": true,
      	"includeBarriers": true,
      	"validateConsistency": true,
      	"validateLocatability": true,
      	"includeIsolated": false,
      	"ignoreBarriersAtStartingPoints": false,
      	"includeUpToFirstSpatialContainer": false,
      	"allowIndeterminateFlow": true,
      	"domainNetworkName": "",
      	"tierName": "",
      	"targetTierName": "",
      	"subnetworkName": "",
      	"diagramTemplateName": "",
      	"shortestPathNetworkAttributeName": "",
      	"filterBitsetNetworkAttributeName": "",
      	"traversabilityScope": "junctionsAndEdges",
      	"conditionBarriers": [],
      	"functionBarriers": [],
      	"arcadeExpressionBarrier": "",
      	"filterBarriers": [],
      	"filterFunctionBarriers": [],
      	"filterScope": "junctionsAndEdges",
      	"functions": [],
      	"nearestNeighbor": {
      		"count": -1,
      		"costNetworkAttributeName": "",
      		"nearestCategories": [],
      		"nearestAssets": []
      	},
      	"outputFilters": [],
      	"outputConditions": [],
      	"propagators": []
      } resultTypes;[
      	{
      		"type": "features",
      		"includeGeometry": true,
      		"includeDomainDescriptions": true,
      		"includePropagatedValues": false,
      		"networkAttributeNames": [
      			"Asset type",
      			"Available Duct Capacity",
      			"Assembly Asset Group",
      			"Asset group",
      			"Ducts Available",
      		],
      		"diagramTemplateName": "",
      		"resultTypeFields": [
      			{
      				"networkSourceId": 11,
      				"fieldName": "devicestatus"
      			},
      			{
      				"networkSourceId": 9,
      				"fieldName": "normaldevicestatus"
      			},
      			{
      				"networkSourceId": 15,
      				"fieldName": "phasescurrent"
      			},
      			{
      				"networkSourceId": 12,
      				"fieldName": "manufacturer"
      			},
      			{
      				"networkSourceId": 14,
      				"fieldName": "phasescurrent"
      			},
      			{
      				"networkSourceId": 10,
      				"fieldName": "sharedneutral"
      			},
      			{
      				"networkSourceId": 6,
      				"fieldName": "addcount"
      			},
      			{
      				"networkSourceId": 8,
      				"fieldName": "ductavailable"
      			},
      			{
      				"networkSourceId": 4,
      				"fieldName": "highvoltagerisercount"
      			},
      			{
      				"networkSourceId": 7,
      				"fieldName": "installdate"
      			},
      			{
      				"networkSourceId": 5,
      				"fieldName": "diameterwidth"
      			},
      			{
      				"networkSourceId": 11,
      				"fieldName": "SUPPORTEDSUBNETWORKNAME"
      			},
      			{
      				"networkSourceId": 9,
      				"fieldName": "loadtapchangepercent"
      			},
      			{
      				"networkSourceId": 15,
      				"fieldName": "phasesenergized"
      			},
      			{
      				"networkSourceId": 12,
      				"fieldName": "maxvoltage"
      			},
      			{
      				"networkSourceId": 14,
      				"fieldName": "TERMINALCONFIGURATION"
      			},
      			{
      				"networkSourceId": 10,
      				"fieldName": "measuredlength"
      			},
      			{
      				"networkSourceId": 6,
      				"fieldName": "materialcode"
      			},
      			{
      				"networkSourceId": 8,
      				"fieldName": "availablecapacity"
      			},
      			{
      				"networkSourceId": 4,
      				"fieldName": "materialcode"
      			},
      			{
      				"networkSourceId": 7,
      				"fieldName": "lifecyclestatus"
      			},
      			{
      				"networkSourceId": 5,
      				"fieldName": "materialsoil"
      			},
      			{
      				"networkSourceId": 11,
      				"fieldName": "lifecyclestatus"
      			},
      			{
      				"networkSourceId": 9,
      				"fieldName": "manufacturer"
      			},
      			{
      				"networkSourceId": 15,
      				"fieldName": "phasesnormal"
      			},
      			{
      				"networkSourceId": 12,
      				"fieldName": "numphasesconstructed"
      			},
      			{
      				"networkSourceId": 14,
      				"fieldName": "phasessubstituted"
      			},
      			{
      				"networkSourceId": 10,
      				"fieldName": "commonconductortype"
      			},
      			{
      				"networkSourceId": 6,
      				"fieldName": "inservicedate"
      			},
      			{
      				"networkSourceId": 8,
      				"fieldName": "assetid"
      			},
      			{
      				"networkSourceId": 4,
      				"fieldName": "foundationtype"
      			},
      			{
      				"networkSourceId": 7,
      				"fieldName": "wallid"
      			},
      			{
      				"networkSourceId": 5,
      				"fieldName": "distance"
      			}
      		]
      	},
      	{
      		"type": "connectivity",
      		"includeGeometry": true,
      		"includeDomainDescriptions": true,
      		"includePropagatedValues": false,
      		"networkAttributeNames": [],
      		"diagramTemplateName": "",
      		"resultTypeFields": []
      	},
      	{
      		"type": "associations",
      		"includeGeometry": true,
      		"includeDomainDescriptions": true,
      		"includePropagatedValues": false,
      		"networkAttributeNames": [],
      		"diagramTemplateName": "",
      		"resultTypeFields": []
      	}
      ]
    CONNECTION_TIMEOUT_LENGTH = 60
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _serverResponse
    TARGET_ATTR_ENCODING = auto-detect
    TARGET_URL = $(HostUrl)/server/rest/services/NapervilleElectric31_SQLServer/UtilityNetworkServer/exportSubnetwork
    TRANSFER_TIMEOUT_LENGTH = 90
    USE_COOKIES = No
    VERIFY_SSL_CERTIFICATES = Yes
    -> JSONFlattener_2
JSONFlattener_2
    ERROR_LIST_ATTR = _json_error
    JSON_DOCUMENT = @Value(_serverResponse)
    NEW_ATTRIBUTES = url
    READ_FROM_FILE = NO
    RECURSIVE = Yes
    -> AttributeManager_3
Note: Export Subnetwork
AttributeManager_3
    ATTR_TABLE:
      REMOVE _http_status_code
      REMOVE _serverResponse
      SET_TO filecopy_source_dataset = @ReplaceRegEx(@Value(url),([^/]+$),"")
      SET_TO featureServerUrl = $(HostUrl)server/rest/services/NapervilleElectric31_SQLServer/FeatureServer
    -> downloadJson

Bookmark: 2-Download JSON result
Note: downloadJson [HTTPCaller] / Request: / Request URL: @Value(url) / HTTP Method: GET / Query String Parameters: / Query String: <not set> / Response: / Save Response Body To: Attribute / Response Body Attribute: _jsonOutput / Response Body Encoding: auto-detect / Response Headers and Status: / List Attribute for Response Headers: <not set> / Status Code Attribute: _http_status_code / Error Attribute: _error / HTTP Client Options: / Save Cookies: No / Follow Redirects: Yes / Verify SSL Certificates: Yes / Connection Timeout Length (seconds): 60 / Transfer Timeout Length (seconds): 90
downloadJson: HTTPCaller
    CONNECTION_TIMEOUT_LENGTH = 60
    ERROR_ATTR = _error
    FOLLOW_REDIRECTS = FOLLOW_WITH_ORIGINAL_METHOD
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _jsonOutput
    TARGET_ATTR_ENCODING = auto-detect
    TARGET_URL = @Value(url)
    TRANSFER_TIMEOUT_LENGTH = 90
    USE_COOKIES = No
    VERIFY_SSL_CERTIFICATES = Yes
    -> JSONFragmenter
JSONFragmenter
    EXPLODE_FORMAT = JSON
    EXTRACT_ATTR = No
    JSON_ATTR = _jsonOutput
    JSON_QUERY = json[*]
    READ_FROM_FILE = NO
    REJECT_EMPTY_LISTS = YES
    FRAGMENTS -> AttributeManager
Note: Download JSON into workflow
AttributeManager
    ATTR_TABLE:
      RENAME_SET_VALUE json_index > json_array
      REMOVE _http_status_code
      REMOVE url
      REMOVE filecopy_source_dataset
      REMOVE token
      REMOVE featureServerUrl
      SET_TO SubnetworkName = $(SubnetworkName)
    USER_EXPOSED_ATTRIBUTES = SubnetworkName
    -> TestFilter

Bookmark: 3-Split JSON into Features
TestFilter
    DEFAULT_VALUE = <UNFILTERED>
    PASSED_TEST_GROUP_OUTPUT = FIRST
    TEST_LIST = "BOOL_OP,OR,COMPOSITE_TEST,""""""1"""""",TEST_CLAUSE,TEST @Value(json_type) = array",array,"BOOL_OP,OR,COMPOSITE_TEST,""""""1"""""",TEST_CLAUSE,TEST @Value(json_type) = object",object
    array -> AttributeFilter_2
    object -> AttributeFilter_4
Note: Split JSON into features
Note: objects
AttributeFilter_4
    ATTR_NAME = json_array
    ATTR_VALUES = sourceMapping,spatialReference,<Empty>,<Missing>,<Null>,<Unfiltered>
    sourceMapping -> JSONFragmenter_6
    spatialReference -> JSONFlattener
JSONFragmenter_6
    EXPLODE_FORMAT = JSON
    EXTRACT_ATTR = Yes
    JSON_ATTR = _jsonOutput
    JSON_QUERY = json[*]
    READ_FROM_FILE = NO
    RECURSIVE = Yes
    REJECT_EMPTY_LISTS = YES
    FRAGMENTS -> Junction_27
Note: SourceMapping intentionally disconnected
Junction_27
Note: Spatial Reference
JSONFlattener
    ERROR_LIST_ATTR = _json_error
    JSON_DOCUMENT = @Value(_jsonOutput)
    NEW_ATTRIBUTES = wkid latestWkid vcsWkid latestVcsWkid
    READ_FROM_FILE = NO
    RECURSIVE = Yes
    -> AttributeCreator
AttributeCreator
    ATTR_TABLE = SET_TO CoordinateSystem = EPSG:@Value(latestWkid)
    -> FeatureMerger_5 [SUPPLIER]
Note: arrays
AttributeFilter_2
    ATTR_NAME = json_array
    ATTR_VALUES = resultTypes,<Empty>,<Missing>,<Null>,<Unfiltered>,featureElements,connectivity,associations,controllers
    featureElements -> JSONFragmenter_2
    connectivity -> JSONFragmenter_3
    associations -> JSONFragmenter_4
    controllers -> JSONFragmenter_5
Note: Controllers
JSONFragmenter_5
    EXPLODE_FORMAT = JSON
    EXTRACT_ATTR = Yes
    JSON_ATTR = _jsonOutput
    JSON_QUERY = json[*]
    READ_FROM_FILE = NO
    RECURSIVE = No
    REJECT_EMPTY_LISTS = YES
    FRAGMENTS -> AttributeExposer_4
AttributeExposer_4
    ATTR_LIST = assetGroupCode,assetGroupName,assetTypeCode,assetTypeName,geometry,globalId,networkSourceId,networkSourceName,objectId,subnetworkHasBeenDeleted,success,terminalId,terminalName,_jsonFormatted,json_index,json_type,moment
    -> FeatureMerger_5 [REQUESTOR]
Note: Feature Elements
JSONFragmenter_2
    EXPLODE_FORMAT = JSON
    EXTRACT_ATTR = Yes
    JSON_ATTR = _jsonOutput
    JSON_QUERY = json[*]
    READ_FROM_FILE = NO
    RECURSIVE = No
    REJECT_EMPTY_LISTS = YES
    FRAGMENTS -> AttributeExposer_2
Note: need to flatten
AttributeExposer_2
    ATTR_LIST = globalId,objectId,networkSourceId,networkSourceName,assetGroupCode,assetGroupName,assetTypeCode,assetTypeName,terminalId,terminalName,_element_index,_jsonFormatted,json_index,json_type,moment,success,subnetworkHasBeenDeleted,positionFrom,positionTo,geometry,fieldValues,networkAttributeValues,networkAttributeDescriptions
    -> DuplicateFilter_4
DuplicateFilter_4
    INPUT_ORDERED_CHOICE = No
    KEYATTR = globalId assetGroupCode assetTypeCode networkSourceId
    UNIQUE -> FeatureMerger_3 [REQUESTOR]
Note: Connectivity
JSONFragmenter_3
    EXPLODE_FORMAT = JSON
    EXTRACT_ATTR = Yes
    JSON_ATTR = _jsonOutput
    JSON_QUERY = json[*]
    READ_FROM_FILE = NO
    RECURSIVE = No
    REJECT_EMPTY_LISTS = YES
    FRAGMENTS -> AttributeExposer_3
AttributeExposer_3
    ATTR_LIST = fromGeometry,fromGlobalId,fromNetworkSourceId,fromNetworkSourceName,fromObjectId,fromTerminalId,fromTerminalName,toGeometry,toGlobalId,toNetworkSourceId,toNetworkSourceName,toObjectId,toTerminalId,toTerminalName,viaGeometry,viaGlobalId,viaNetworkSourceId,viaNetworkSourceName,viaObjectId,viaPositionFrom,viaPositionTo,_jsonFormatted,json_index,json_type,moment,subnetworkHasBeenDeleted,success
    -> TestFilter_3
Note: Test for associations and duplicate features
TestFilter_3
    DEFAULT_VALUE = featureElementsDupl
    PASSED_TEST_GROUP_OUTPUT = FIRST
    TEST_LIST = "BOOL_OP,OR,COMPOSITE_TEST,""""""1"""""",TEST_CLAUSE,TEST @Value(viaNetworkSourceId) = 1",associations
    associations -> FeatureMerger_2 [REQUESTOR]
Note: Associations
JSONFragmenter_4
    EXPLODE_FORMAT = JSON
    EXTRACT_ATTR = Yes
    JSON_ATTR = _jsonOutput
    JSON_QUERY = json[*]
    READ_FROM_FILE = NO
    RECURSIVE = No
    REJECT_EMPTY_LISTS = YES
    FRAGMENTS -> AttributeExposer_5
AttributeExposer_5
    ATTR_LIST = associationType,fromGlobalId,fromNetworkSourceId,fromNetworkSourceName,fromTerminalId,fromTerminalName,subnetworkHasBeenDeleted,toGlobalId,toNetworkSourceId,toNetworkSourceName,toTerminalId,toTerminalName,_jsonFormatted,json_index,json_type,moment,success
    -> AttributeExposer_5_Output

Bookmark: 4-Feature creation
Note: controller/s
FeatureMerger_5
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> GeometryReplacer_5
    USED_SUPPLIER -> FeatureMerger_3 [SUPPLIER]
GeometryReplacer_5
    KIND_LONG = Esri JSON
    REMOVE_ATTRIBUTE = No
    SOURCE = @Value(geometry)
    -> EsriReprojector_3
EsriReprojector_3
    DEST = @Value(CoordinateSystem)
    GEOTRANSFORMATION_NAME = <None>
    INTERPOLATION_TYPE_NAME = Nearest Neighbor
    RASTER_CELL_SIZE = Preserve Cells
    RASTER_TOLERANCE = 0.0
    SOURCE = @Value(CoordinateSystem)
    REPROJECTED -> GeometryReplacer_5_Output
GeometryReplacer_5_Output: Logger
    LOG_FEATURE = LOG_ONLY
    MAXCOORDS = 20
    MAXFEATS = 20
    MESSAGE = Feature is:
    SEVERITY = INFO
    LOGGED -> Junction_26
Note: Controller intentionally disconected
Note: Feature Creation
Junction_26
Note: featureElements
FeatureMerger_3
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> DuplicateFilter_3
    USED_SUPPLIER -> FeatureMerger_2 [SUPPLIER]
DuplicateFilter_3
    INPUT_ORDERED_CHOICE = No
    KEYATTR = globalId assetGroupCode assetTypeCode networkSourceId
    UNIQUE -> TestFilter_2
Note: Test for system junctions and duplicate associations
TestFilter_2
    DEFAULT_VALUE = associationDuplicates
    PASSED_TEST_GROUP_OUTPUT = FIRST
    TEST_LIST = "BOOL_OP,OR,COMPOSITE_TEST,""""""1"""""",TEST_CLAUSE,TEST @Value(networkSourceId) > 2",featureElements,"BOOL_OP,OR,COMPOSITE_TEST,""""""1"""""",TEST_CLAUSE,TEST @Value(networkSourceId) = 2",systemJunctions
    featureElements -> AttributeRenamer
    featureElements -> GeometryReplacer_2
    systemJunctions -> Junction_5
Note: Feature Elements plus result fields
FeatureMerger
    ATTR_ACCUM_MODE = Merge Supplier
    ATTR_CONFLICT_RES = Use Requestor
    CLEANING_TOLERANCE = Automatic
    CONNECT_Z_MODE = First Wins
    GEOM_TYPE = Build Polygons
    IGNORE_NULLS = No
    JOIN_KEYS = @Value(json_index) @Value(row_index) AUTO
    MERGE_TYPE = Attributes Only
    PROCESS_DUPS = YES
    REJECT_NULL_MISSING_KEYS = No
    SUPPLIERS_FIRST = No
    MERGED -> AttributeFilter
    UNMERGED_REQUESTOR -> AttributeFilter
Note: System junctions Left disconnected.
Junction_5
FeatureMerger_2
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> Cloner_2
Note: connectivity
Cloner_2
    COPIES = 2
    COPYATT = _copynum
    COPY -> fromGeometry
    COPY -> toGeometry
fromGeometry: GeometryReplacer
    KIND_LONG = Esri JSON
    REMOVE_ATTRIBUTE = No
    SOURCE = @Value(fromGeometry)
    -> EsriReprojector_2
EsriReprojector_2
    DEST = @Value(CoordinateSystem)
    GEOTRANSFORMATION_NAME = <None>
    INTERPOLATION_TYPE_NAME = Nearest Neighbor
    RASTER_CELL_SIZE = Preserve Cells
    RASTER_TOLERANCE = 0.0
    SOURCE = @Value(CoordinateSystem)
    REPROJECTED -> LineBuilder_2
toGeometry: GeometryReplacer
    KIND_LONG = Esri JSON
    REMOVE_ATTRIBUTE = No
    SOURCE = @Value(toGeometry)
    -> EsriReprojector_4
EsriReprojector_4
    DEST = @Value(CoordinateSystem)
    GEOTRANSFORMATION_NAME = <None>
    INTERPOLATION_TYPE_NAME = Nearest Neighbor
    RASTER_CELL_SIZE = Preserve Cells
    RASTER_TOLERANCE = 0.0
    SOURCE = @Value(CoordinateSystem)
    REPROJECTED -> LineBuilder_2
LineBuilder_2
    ACCUM_INPUT_ATTRS = Use Attributes From One Feature
    GROUP_BY = json_index
    REMOVE_DUPLICATES = Yes
    LINE -> AttributeFilter
AttributeFilter
    ATTR_NAME = json_array
    ATTR_VALUES = <Empty>,<Missing>,<Null>,<Unfiltered>,connectivity,featureElements
    connectivity -> AttributeKeeper_6
    featureElements -> AttributeKeeper_13
AttributeKeeper_6
    CREATE_BULK_MODE_FEATURES = NO
    KEEP_ATTRS = assetGroupName,globalId,networkSourceId,assetTypeName,objectId,json_array,SubnetworkName,networkSourceName,terminalName
    -> SchemaSetter_2 [Input_2]
AttributeKeeper_13
    CREATE_BULK_MODE_FEATURES = NO
    KEEP_ATTRS = json_array,SubnetworkName,assetGroupName,assetTypeName,globalId,networkSourceName,objectId,terminalName,commonconductortype,commonconductortype_resolved,lifecyclestatus,lifecyclestatus_resolved,maxvoltage,maxvoltage_resolved,measuredlength,normaldevicestatus,normaldevicestatus_resolved,numphasesconstructed,numphasesconstructed_resolved,sharedneutral,sharedneutral_resolved,SUPPORTEDSUBNETWORKNAME
    -> SchemaSetter [Input_2]
Note: associations
AttributeExposer_5_Output: Logger
    LOG_FEATURE = LOG_ONLY
    MAXCOORDS = 20
    MAXFEATS = 20
    MESSAGE = Feature is:
    SEVERITY = INFO
    LOGGED -> DuplicateFilter_2
DuplicateFilter_2
    INPUT_ORDERED_CHOICE = No
    KEYATTR = fromGlobalId fromNetworkSourceId fromTerminalId toGlobalId toNetworkSourceId toTerminalId
    UNIQUE -> AttributeFilter_3
AttributeFilter_3
    ATTR_NAME = associationType
    ATTR_VALUES = <Empty>,<Missing>,<Null>,<Unfiltered>,attachment,containment
    attachment -> AttributeKeeper_2
    containment -> AttributeKeeper_3
Note: structural attachments
AttributeKeeper_2
    CREATE_BULK_MODE_FEATURES = NO
    KEEP_ATTRS = toGlobalId,fromGlobalId,json_array,SubnetworkName,fromNetworkSourceName,fromTerminalName,toNetworkSourceName,toTerminalName,associationType
    -> SchemaSetter_3 [Input_2]
Note: containments
AttributeKeeper_3
    CREATE_BULK_MODE_FEATURES = NO
    KEEP_ATTRS = toGlobalId,fromGlobalId,json_array,SubnetworkName,associationType,fromNetworkSourceName,fromTerminalName,toNetworkSourceName,toTerminalName
    -> SchemaSetter_3 [Input_2]

Bookmark: FieldValues, NetworkAttributes and Descriptions
GeometryReplacer_2
    KIND_LONG = Esri JSON
    REMOVE_ATTRIBUTE = No
    SOURCE = @Value(geometry)
    -> EsriReprojector
EsriReprojector
    DEST = @Value(CoordinateSystem)
    GEOTRANSFORMATION_NAME = <None>
    INTERPOLATION_TYPE_NAME = Nearest Neighbor
    RASTER_CELL_SIZE = Preserve Cells
    RASTER_TOLERANCE = 0.0
    SOURCE = @Value(CoordinateSystem)
    REPROJECTED -> FeatureMerger [REQUESTOR]
Note: fieldValues
AttributeRenamer
    ATTR_TABLE = RENAME_SET_DEFAULT json_index > row_index
    MISSING_INPUT_ATTRS = REMOVE
    -> AttributeKeeper
    -> AttributeKeeper_7
AttributeKeeper
    CREATE_BULK_MODE_FEATURES = NO
    KEEP_ATTRS = fieldValues,row_index
    -> JSONFragmenter_7
JSONFragmenter_7
    EXPLODE_FORMAT = JSON
    EXTRACT_ATTR = Yes
    JSON_ATTR = fieldValues
    JSON_QUERY = json[*]
    NEW_ATTRIBUTES = fieldName description value
    READ_FROM_FILE = NO
    RECURSIVE = Yes
    REJECT_EMPTY_LISTS = YES
    FRAGMENTS -> AttributeKeeper_4
AttributeKeeper_4
    CREATE_BULK_MODE_FEATURES = NO
    KEEP_ATTRS = description,fieldName,row_index,value
    -> AttributeCreator_3
AttributeCreator_3
    ATTR_TABLE:
      SET_TO @Value(fieldName) = @Value(value)
      SET_TO @Value(fieldName)_resolved = @Value(description)
    -> AttributeExposer
AttributeExposer
    ATTR_LIST = commonconductortype,commonconductortype_resolved,lifecyclestatus,lifecyclestatus_resolved,maxvoltage,maxvoltage_resolved,measuredlength,normaldevicestatus,normaldevicestatus_resolved,numphasesconstructed,numphasesconstructed_resolved,row_index,sharedneutral,sharedneutral_resolved,SUPPORTEDSUBNETWORKNAME
    -> AttributeKeeper_5
AttributeKeeper_5
    CREATE_BULK_MODE_FEATURES = NO
    KEEP_ATTRS = commonconductortype,commonconductortype_resolved,lifecyclestatus,lifecyclestatus_resolved,maxvoltage,maxvoltage_resolved,measuredlength,normaldevicestatus,normaldevicestatus_resolved,numphasesconstructed,numphasesconstructed_resolved,row_index,sharedneutral,sharedneutral_resolved,SUPPORTEDSUBNETWORKNAME
    -> Aggregator
Aggregator
    ACCUM_ATTRS_NAME = Merge Incoming Attributes
    GROUP_BY = row_index
    MODE = Attributes Only
    SEP = ,
    AGGREGATE -> Sorter
Sorter
    SORT_PARM = row_index NATURAL ASCENDING
    SORTED -> FeatureMerger [SUPPLIER]
Note: networkAttributes
AttributeKeeper_7
    CREATE_BULK_MODE_FEATURES = NO
    KEEP_ATTRS = row_index,networkAttributeValues,networkAttributeDescriptions
    -> JSONFragmenter_9
    -> JSONFragmenter_8
Note: networkAttributeValue
JSONFragmenter_9
    EXPLODE_FORMAT = JSON
    EXTRACT_ATTR = Yes
    JSON_ATTR = networkAttributeValues
    JSON_QUERY = json[*]
    NEW_ATTRIBUTES = Asset group Asset type
    READ_FROM_FILE = NO
    RECURSIVE = Yes
    REJECT_EMPTY_LISTS = YES
    FRAGMENTS -> AttributeManager_4
AttributeManager_4
    ATTR_TABLE:
      RENAME_SET_VALUE Asset group > NetworkAttributeAsset group
      RENAME_SET_VALUE Asset type > NetworkAttributeAsset type
      REMOVE networkAttributeValues
      REMOVE networkAttributeDescriptions
      REMOVE json_type
      REMOVE json_index
    -> Aggregator_2
Aggregator_2
    ACCUM_ATTRS_NAME = Merge Incoming Attributes
    GROUP_BY = row_index
    MODE = Attributes Only
    SEP = ,
    AGGREGATE -> Sorter_2
Sorter_2
    SORT_PARM = row_index NUMERIC ASCENDING
    SORTED -> FeatureMerger [SUPPLIER]
Note: networkAttributeDescription
JSONFragmenter_8
    EXPLODE_FORMAT = JSON
    EXTRACT_ATTR = Yes
    JSON_ATTR = networkAttributeDescriptions
    JSON_QUERY = json[*]
    NEW_ATTRIBUTES = Asset type
    READ_FROM_FILE = NO
    RECURSIVE = Yes
    REJECT_EMPTY_LISTS = YES
    FRAGMENTS -> AttributeManager_2
AttributeManager_2
    ATTR_TABLE:
      REMOVE networkAttributeValues
      REMOVE networkAttributeDescriptions
      REMOVE json_type
      REMOVE json_index
      RENAME_SET_VALUE Asset type > NetworkAttributeAsset type_resolved
    -> Sorter_3
Sorter_3
    SORT_PARM = row_index NUMERIC ASCENDING
    SORTED -> FeatureMerger [SUPPLIER]

Bookmark: 5-Schema Setting and Output
Note: Schema settings and Outputs
Note: Connectivity
SchemaSetter_2
    ForceDataType = No
    SORT = None
    Output_2 -> Junction
    Output_2 -> Junction_9
    Output_2 -> Junction_17
    Output_2 -> Junction_6
Junction
    -> Junction_2
Junction_2
    -> FeatureWriter [Output_200]
Junction_9
    -> Junction_10
Junction_10
    -> FeatureWriter_2 [Output_200]
Junction_17
    -> Junction_18
Junction_18
    -> FeatureWriter_3 [Output_200]
Junction_6
    -> CsmapReprojector
CsmapReprojector
    DEST = EPSG:3435
    INTERPOLATION_TYPE_NAME = Nearest Neighbor
    RASTER_CELL_SIZE = Preserve Cells
    RASTER_TOLERANCE = 0.0
    REPROJECTED -> Junction_13
Junction_13
    -> FeatureWriter_4 [Output_200]
Note: feature elements
SchemaSetter
    ForceDataType = No
    SORT = None
    Output_2 -> Junction_3
    Output_2 -> Junction_11
    Output_2 -> Junction_19
    Output_2 -> Junction_14
Junction_3
    -> Junction_4
Junction_4
    -> FeatureWriter [Output_2]
Junction_11
    -> Junction_12
Junction_12
    -> FeatureWriter_2 [Output_2]
Junction_19
    -> Junction_20
Junction_20
    -> FeatureWriter_3 [Output_2]
Junction_14
    -> CsmapReprojector_2
CsmapReprojector_2
    DEST = EPSG:3435
    INTERPOLATION_TYPE_NAME = Nearest Neighbor
    RASTER_CELL_SIZE = Preserve Cells
    RASTER_TOLERANCE = 0.0
    REPROJECTED -> Junction_21
Junction_21
    -> FeatureWriter_4 [Output_2]
Note: Attachment and Containments
SchemaSetter_3
    ForceDataType = No
    SORT = None
    Output_2 -> Junction_7
    Output_2 -> Junction_15
    Output_2 -> Junction_23
    Output_2 -> Junction_22
Junction_7
    -> Junction_8
Junction_8
    -> FeatureWriter [Output_201]
Note: File GDB
FeatureWriter
    DATASET = C:\data\output\fgdb\@Value(SubnetworkName).gdb
    DATASET_ATTR = _dataset
    FEATURE_TYPE_LIST_ATTR = _feature_type
    FILEGDB_COORDINATE_SYSTEM_GRANULARITY = FEATURE_TYPE
    FILEGDB_DESTINATION_DATASETTYPE_VALIDATION = Yes
    FILEGDB_ENABLE_LOAD_ONLY_MODE = YES
    FILEGDB_OVERWRITE_GEODB = YES
    FILEGDB_WRITE_UNZONED_UTC = No
    FORMAT = FILEGDB
    TOTAL_FEATURES_WRITTEN_ATTR = _total_features_written
Junction_15
    -> Junction_16
Junction_16
    -> FeatureWriter_2 [Output_201]
Note: Mobile GDB
FeatureWriter_2
    DATASET = C:\data\output\mgdb\@Value(SubnetworkName).geodatabase
    DATASET_ATTR = _dataset
    ESRI_MOBILE_GEODATABASE_ANNOTATION_UNITS = unknown_units
    ESRI_MOBILE_GEODATABASE_COORDINATE_SYSTEM_GRANULARITY = FEATURE_TYPE
    ESRI_MOBILE_GEODATABASE_DEFAULT_Z_VALUE = 0
    ESRI_MOBILE_GEODATABASE_DESTINATION_DATASETTYPE_VALIDATION = Yes
    ESRI_MOBILE_GEODATABASE_DUMP_FAILED_FEATURES = no
    ESRI_MOBILE_GEODATABASE_ENABLE_FAST_DELETES = yes
    ESRI_MOBILE_GEODATABASE_ENABLE_LOAD_ONLY_MODE = no
    ESRI_MOBILE_GEODATABASE_GRID_1 = 0
    ESRI_MOBILE_GEODATABASE_HAS_MEASURES = no
    ESRI_MOBILE_GEODATABASE_HAS_Z_VALUES = auto_detect
    ESRI_MOBILE_GEODATABASE_IGNORE_FAILED_FEATURE_ENTRY = no
    ESRI_MOBILE_GEODATABASE_MAX_NUMBER_FAILED_FEATURES = -1
    ESRI_MOBILE_GEODATABASE_OVERWRITE_GEODB = YES
    ESRI_MOBILE_GEODATABASE_REQUESTED_GEODATABASE_VERSION = CURRENT
    ESRI_MOBILE_GEODATABASE_SIMPLIFY_GEOM = No
    ESRI_MOBILE_GEODATABASE_SIMPLIFY_NETWORK_FEATURES = no
    ESRI_MOBILE_GEODATABASE_TRANSACTION = 0
    ESRI_MOBILE_GEODATABASE_TRANSACTION_INTERVAL = 1000
    ESRI_MOBILE_GEODATABASE_TRANSACTION_TYPE = TRANSACTIONS
    ESRI_MOBILE_GEODATABASE_VALIDATE_FEATURES = no
    ESRI_MOBILE_GEODATABASE_XY_SCALE = 0
    ESRI_MOBILE_GEODATABASE_X_ORIGIN = 0
    ESRI_MOBILE_GEODATABASE_Y_ORIGIN = 0
    ESRI_MOBILE_GEODATABASE_Z_ORIGIN = 0
    ESRI_MOBILE_GEODATABASE_Z_SCALE = 0
    FEATURE_TYPE_LIST_ATTR = _feature_type
    FORMAT = ESRI_MOBILE_GEODATABASE
    TOTAL_FEATURES_WRITTEN_ATTR = _total_features_written
Junction_23
    -> Junction_24
Junction_24
    -> FeatureWriter_3 [Output_201]
Note: SHAPEFILE
FeatureWriter_3
    DATASET = C:\data\output\shp\@Value(SubnetworkName)
    DATASET_ATTR = _dataset
    ESRISHAPE_COMPRESSED_SHAPE_FILE = No
    ESRISHAPE_DESTINATION_DATASETTYPE_VALIDATION = Yes
    ESRISHAPE_DIMENSION = auto
    ESRISHAPE_ENCODING = fme-source-encoding
    ESRISHAPE_MEASURES_AS_Z = no
    ESRISHAPE_PRESERVE_RING_VERTEX_ORDER = No
    ESRISHAPE_STRICT_COMPATIBILITY = Yes
    ESRISHAPE_SURFACE_AND_SOLID_STORAGE = shape_multipatch
    ESRISHAPE_UPPER_CASE_ATTR_NAMES = No
    ESRISHAPE_WRITE_SPATIAL_INDEX = No
    FEATURE_TYPE_LIST_ATTR = _feature_type
    FORMAT = ESRISHAPE
    TOTAL_FEATURES_WRITTEN_ATTR = _total_features_written
Junction_22
    -> Junction_25
Junction_25
    -> FeatureWriter_4 [Output_201]
Note: DGN
FeatureWriter_4
    DATASET = C:\data\output\dgn\@Value(SubnetworkName).dgn
    DATASET_ATTR = _dataset
    DGNV8_ALLOW_FILL = YES
    DGNV8_CELL_ENCODING = windows-1252
    DGNV8_CELL_LIBRARY = $(FME_MF_DIR)1/design/default_v8.cel
    DGNV8_CREATE_LINE_ELEMENTS = YES
    DGNV8_DESTINATION_DATASETTYPE_VALIDATION = Yes
    DGNV8_METAFILE = DGNV8
    DGNV8_OUT_UNITS = IGDS_MASTER_UNITS
    DGNV8_SCALE_CELL_MODELS = YES
    DGNV8_SEED_ENCODING = windows-1252
    DGNV8_SEED_FILE = $(FME_MF_DIR)1/design/seed3d_ft_v8.dgn
    DGNV8_WRITE_COORDINATE_SYSTEMS = YES
    DGNV8_WRITE_TAGS = NO
    DGNV8_WRITE_TRUE_COLORS = YES
    DGNV8_WRITE_XFM_DGNSTORES_FROM_SEED = YES
    DGNV8_WRITING_TO_V8 = YES
    FEATURE_TYPE_LIST_ATTR = _feature_type
    FORMAT = DGNV8
    TOTAL_FEATURES_WRITTEN_ATTR = _total_features_written

FME custom transformer SchemaSetter
This transformer adds both exposed and unexposed attributes to a feature-based schema, with appropriate data types. 
For example: if a feature has the following attributes:
Attribute(boolean) : 'mybool' has value 'Yes' 
Attribute(32 bit integer): 'myint' has value '12' 
Attribute(64 bit real) : 'myreal' has value '12.965' 
the following list attributes will be added:
Attribute(string) : 'attribute{0}.fme_data_type' has value 'fme_boolean' 
Attribute(encoded: utf-8): 'attribute{0}.name' has value 'mybool' 
Attribute(string) : 'attribute{1}.fme_data_type' has value 'fme_int32' 
Attribute(encoded: utf-8): 'attribute{1}.name' has value 'myint' 
Attribute(string) : 'attribute{2}.fme_data_type' has value 'fme_real64' 
Attribute(encoded: utf-8): 'attribute{2}.name' has value 'myreal' 
The transformer also gives users the option to exclude certain attributes based on name or prefix, and automatically excludes all "fme_" attributes.  Another option exists to force all attributes to string data type in the case of mismatches in the source attributes.
Input Ports 
Features containing attributes for which a schema definition is required. 
Output Ports 
All features are output. Attributes which have been selected to be excluded are removed from the feature. The list containing the schema of the feature is added to each feature. 
Parameters 
Attributes to Exclude 
A selected set of attributes that will be excluded from the generated schema list and removed from the feature.
Prefixes to Exclude 
A comma-delimited list of prefixes for attributes that are to be excluded from the generated schema list and removed from the feature. Regular expressions are not supported. For example: "date" will exclude any attributes that start with the letters "date" e.g. date_created, dateupdated
Sort Attributes 
(Ascending, Descending, None) Set this parameter to alphabetically sort output attributes.
Force attributes to strings:
If set to "No", the SchemaSetter will set the data type to the native attribute data type. If set to "Yes", the SchemaSetter will force all attribute data type sto "fme_char(255)".
Usage Notes 
The feature based schema can be passed to any writer that it set to Dynamic Mode and used with the "Schema from First Feature" setting.
Please see https://knowledge.safe.com/articles/1051/dynamic-workflow-tutorial-destination-schema-is-de-2.html for more information on feature-based schema using list attributes.

Parameters:
- AttributesToExclude =   # " " Attributes to exclude
- PrefixesToExclude =   # Prefixes to exclude
- SORT = None   # Sort Attributes
- ForceDataType = No   # Force attributes to strings?

Input_2 (input)
    -> ParameterFetcher
Note: Retrieve Parameters
ParameterFetcher
    ATTR_LIST = _AttributesToExclude $(AttributesToExclude) _PrefixesToExclude $(PrefixesToExclude) _sort $(SORT) _ForceDataType $(ForceDataType)
    -> PythonCaller
Note: See Comment in Code
PythonCaller
    PYTHONSOURCE:
      from __future__ import absolute_import, division, print_function, unicode_literals

      import fmeobjects
      import six

      #Checks if a list entry starts with a certain string
      def StringLikeList(list,string):
              test=False
              for element in list:
                  if string.startswith(element):
                      test=True
              return test

       # Checks if a list contains an element equal to a certain string
      def StringInList(list,string):
              test=False
              for element in list:
                  if string==element:
                      test=True
              return test

      # Template Class Interface:
      class FeatureProcessor(object):

          typesMapping = {
              fmeobjects.FME_ATTR_UNDEFINED : None,
              fmeobjects.FME_ATTR_BOOLEAN : "fme_boolean",
              fmeobjects.FME_ATTR_INT8 : "fme_int8",
              fmeobjects.FME_ATTR_UINT8 : "fme_uint8",
              fmeobjects.FME_ATTR_INT16 : "fme_int16",
              fmeobjects.FME_ATTR_UINT16 : "fme_uint16",
              fmeobjects.FME_ATTR_INT32 : "fme_int32",
              fmeobjects.FME_ATTR_UINT32 : "fme_uint32",
              fmeobjects.FME_ATTR_REAL32 : "fme_real32",
              fmeobjects.FME_ATTR_REAL64 : "fme_real64",
              fmeobjects.FME_ATTR_REAL80 : "fme_real80",
              fmeobjects.FME_ATTR_STRING : "fme_char(255)",
              fmeobjects.FME_ATTR_ENCODED_STRING : "fme_varchar(255)",
              fmeobjects.FME_ATTR_INT64 : "fme_int64",
              fmeobjects.FME_ATTR_UINT64 : "fme_uint64"
           }

          def __init__(self):
              pass
          def input(self,feature):
              #create a new feature
              nfeature=fmeobjects.FMEFeature()
              #get list of all attributes on feature
              attlist=feature.getAllAttributeNames()
              #loop through all attributes and add to schema if they fail exclusion criteria
              i=0
              ExcludedAttributes=str(feature.getAttribute('_AttributesToExclude')).split(",")
              ExcludedAttributes.append('_ForceDataType')
              ExcludedPrefixes=str(feature.getAttribute('_PrefixesToExclude')).split(",")

              # remove all fme_ attributes from list - don't want to include these in dynamic schema
              ExcludedPrefixes = ['fme_'] if ExcludedPrefixes == [''] else ExcludedPrefixes + ["fme_"]

              # sorting attributes
              if feature.getAttribute('_sort') == 'Ascending' or feature.getAttribute('_sort') == 'Descending':
                  attlist.sort()
                  if feature.getAttribute('_sort') == 'Descending':
                      attlist.reverse()

              for att in attlist:
                  if not StringInList(ExcludedAttributes,att) and not StringLikeList(ExcludedPrefixes,att) and not att=='_AttributesToExclude' and not att=='_PrefixesToExclude' and not att=='_sort':

                     #Check datatype and set in schema
                     if feature.getAttribute('_ForceDataType') == 'No':
                         type = feature.getAttributeType(att)
                         type = self.typesMapping[type]
                     #Force to string if user wishes
                     else:
                         type = "fme_char(255)"

                     if type is None:
                         feature.removeAttribute(att)
                     else:
                         #add schema attributes to feature
                         nfeature.setAttribute("attribute{"+str(i)+"}.fme_data_type",type)
                         nfeature.setAttribute("attribute{"+str(i)+"}.name",six.text_type(att))
                         nfeature.setAttribute(att,feature.getAttribute(att))
                         i+=1;
              #copy original geometry to new feature
              nfeature.setGeometry(feature.getGeometry())
              nfeature.setCoordSys(feature.getCoordSys())
              nfeature.setFeatureType(feature.getFeatureType())
              nfeature.setAttribute("fme_geometry{0}",feature.getAttribute("fme_type"))
              nfeature.setAttribute("fme_feature_type",feature.getAttribute("fme_feature_type"))
              print(i)
              self.pyoutput(nfeature)
          def close(self):
              pass
    PYTHONSYMBOL = FeatureProcessor
    -> Output_2 (output)
Output_2 (output)

FME custom transformer EsriPortalTokenGetter
Generate an ArcGIS Enterprise Portal service token.
This transformer uses your portal's REST API to generate a service token you can use in subsequent operations requiring one.  For example if you construct an HTTP request to call an administrative or secured endpoint you can include the token.
Enter your portal base URL, web adaptor name, credentials and token expiration lifespan in minutes.
See this topic for background on ArcGIS URL components

Parameters:
- PortalURL = https://webadaptorhost.domain.com   # https Portal Base URL
- PortalWebadaptor = portal   # Portal Webadaptor
- PortalUser = portal_user   # Portal User
- PortalPassword =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   # Enter a Password
- Expiration = 60   # Expiration Duration

Creator
    GEOMTYPE = Geometry Object
    NUM = 1
    CREATED -> AttributeManager_2
AttributeManager_2
    ATTR_TABLE:
      SET_TO PortalURL = $(PortalURL)
      SET_TO PortalWebadaptor = $(PortalWebadaptor)
      SET_TO PortalUser = $(PortalUser)
      SET_TO PortalPassword = $(PortalPassword)
      SET_TO ExpirationMinutes = $(Expiration)
    -> EsriPortalTokenGetter
EsriPortalTokenGetter: PythonCaller
    NEW_ATTRIBUTES = token
    PYTHONSOURCE:
      import fme
      import fmeobjects
      import requests

      class FeatureProcessor(object):
          def __init__(self):
              pass
          def input(self, feature):
              portal = feature.getAttribute('PortalURL')
              webadaptor = feature.getAttribute('PortalWebadaptor')
              url = '/'.join([portal,webadaptor,'sharing','rest','generateToken'])
              referer = portal
              body = {'username': feature.getAttribute('PortalUser'),
              'password': feature.getAttribute('PortalPassword'),
              'client': 'referer',
              'referer': referer,
              'f': 'json',
              'expiration': feature.getAttribute('ExpirationMinutes')}
              response = requests.post(url, headers={}, data=body).json()
              token = str(response['token'])
              feature.setAttribute('token',token)
              self.pyoutput(feature)
          def close(self):
              pass
          def process_group(self):
              pass
    PYTHONSYMBOL = FeatureProcessor
    -> AttributeKeeper
AttributeKeeper
    CREATE_BULK_MODE_FEATURES = NO
    KEEP_ATTRS = token
    -> Output (output)
Output (output)
