FME workspace BOundaryAll.fmw

Parameters:
- SourceDataset_CSV2 =

Readers:
- CSV2_1: CSV2 from $(SourceDataset_CSV2)

CSV (reader CSV2_1)
    attributes: _name varchar(56), _full_path varchar(57), _url varchar(110), _bucket_name varchar(18), _relative_path varchar(57)
    -> S3Connector
S3Connector
    CREDENTIAL_SOURCE = Anonymous
    OPERATION_TYPE = List
    PARAMETER_SETUP = _FME_BUCKET]usgs-lidar-public]_FME_FILES]@Value(_name)]_FME_INCLUDE_SUBFOLDERS]No]_FME_OBJECT_NAME_ATTRIBUTE]_name]_FME_OBJECT_ID_ATTRIBUTE]_bucket_name]_FME_OBJECT_PATH_ATTRIBUTE]_full_path]_FME_OBJECT_URL_ATTRIBUTE]_url]_FME_OBJECT_SIZE_ATTRIBUTE]_file_size]_FME_OBJECT_MODIFIED_ATTRIBUTE]_file_last_modified]_FME_OBJECT_TYPE_ATTRIBUTE]_file_or_folder]_FME_OBJECT_RELATIVE_PATH_ATTRIBUTE]_relative_path]FME_CONTROLLER_QUERY_FILE]amazons3_deps/List.fme]FME_CONTROLLER_CHOICE]List
    _FME_S3_AWS_REGION = us-west-2
    _FME_S3_VERIFY_SSL = yes
    -> TestFilter
TestFilter
    DEFAULT_VALUE = <UNFILTERED>
    TEST_LIST = "BOOL_OP,OR,COMPOSITE_TEST,""""""1"""""",TEST_CLAUSE,CASE_INSENSITIVE_TEST @Value(_name) = ept.json",EPT_Dataset,"BOOL_OP,OR,COMPOSITE_TEST,""""""1"""""",TEST_CLAUSE,CASE_INSENSITIVE_TEST @Value(_name) CONTAINS .json",JSON
    EPT_Dataset -> FeatureReader_2 [INITIATOR]
FeatureReader_2
    ATTRS_TO_EXPOSE = json_fragment
    ATTR_ACCUM_MODE = Merge Initiator and Result
    ATTR_CONFLICT_RES = Use Result
    ATTR_IGNORE_NULLS = No
    COMBINE_GEOM = Use Result
    DATASET = @Value(_url)
    FORMAT = JSON
    JSON_COORDINATE_SYSTEM_KEY = json_ogc_wkt_crs
    JSON_DECODE_TEXT_STRINGS = Yes
    JSON_FEATURE_TYPE_KEY = json_featuretype
    JSON_FLATTEN_MODE = ALL_LEVELS
    JSON_GEOMETRY_FORMAT = GeoJSON
    JSON_GEOMETRY_KEY = json_geometry
    JSON_SAVE_FRAGMENTS = YES
    JSON_SCAN_MODE = AUTO
    JSON_USE_BASENAME_AS_DEFAULT_FEATURE_TYPE = No
    JSON_USE_SEARCH_ENVELOPE = NO
    OUTPUT_FEATURES_DISPLAY = Schema and Data Features
    <OTHER> -> JSONFormatter
JSONFormatter
    ERROR_LIST_ATTR = _json_error
    FORMAT = Pretty Print
    INDENT_STYLE = 3 spaces
    JSON_DOCUMENT = @Value(json_fragment)
    OUTPUT_ATTR = _formatted
    OUTPUT_ENCODING = UTF-8
    READ_FROM_FILE = NO
    REMOVE_EMPTY_OBJECTS_AND_ARRAYS = No
    REMOVE_EMPTY_STRINGS = No
    REMOVE_NULLS = No
    -> JSONFlattener
JSONFlattener
    ERROR_LIST_ATTR = _json_error
    JSON_DOCUMENT = @Value(json_fragment)
    READ_FROM_FILE = NO
    RECURSIVE = Yes
    -> AttributeExposer
AttributeExposer
    ATTR_LIST = bounds{},srs.wkt,srs.horizontal
    -> AttributeManager
AttributeManager
    ATTR_TABLE:
      RENAME_SET_VALUE bounds{0} > xmin
      RENAME_SET_VALUE bounds{1} > ymin
      RENAME_SET_VALUE bounds{2} > zmin
      RENAME_SET_VALUE bounds{3} > xmax
      RENAME_SET_VALUE bounds{4} > ymax
      RENAME_SET_VALUE bounds{5} > zmax
    -> CoordinateSystemDescriptionConverter
CoordinateSystemDescriptionConverter
    DIRECTION_LONG = Convert To FME Representation
    KIND_LONG = EPSG Number
    SRC = srs.horizontal
    VAL_ATTR = _newcoordsys
    -> VertexCreator
VertexCreator
    MEASURE_TYPE = Continuous
    MODE_NAME = Replace with Point
    XVAL = @Value(xmin)
    YVAL = @Value(ymin)
    ZVAL = @Value(zmin)
    -> VertexCreator_2
VertexCreator_2
    MEASURE_TYPE = Continuous
    MISSING_VAL_MODE = Compute
    MODE_NAME = Add Point
    XVAL = @Value(xmax)
    YVAL = @Value(ymax)
    ZVAL = @Value(zmax)
    -> BoundingBoxAccumulator
BoundingBoxAccumulator
    ACCUM_ATTRS_NAME = Merge Incoming Attributes
    GROUP_BY = _full_path
    BOUNDING_BOX -> Tester
Note: Tester [Tester] / Test Clauses: Left ValueOperatorRight Value@Value(_full_path)ContainsVA_ Comparison Mode: Case Insensitive / Advanced: / Preserve Feature Order: Per Output Port
Tester
    BOOL_OP = OR
    COMPOSITE_TEST = 1
    TEST_CLAUSE = CASE_INSENSITIVE_TEST @Value(_full_path) CONTAINS VA_
    TEST_MODE = TEST
    PASSED -> Boundary
Boundary: Inspector
Creator
    GEOMTYPE = Geometry Object
    NUM = 1
